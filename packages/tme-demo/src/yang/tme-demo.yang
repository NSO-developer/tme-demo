module tme-demo {

  yang-version 1.1;
  namespace "http://example.com/tme-demo";
  prefix tme-demo;

  import ietf-inet-types {
    prefix inet;
  }
  import tailf-common {
    prefix tailf;
  }
  import tailf-ncs {
    prefix ncs;
  }
  import l3vpn {
    prefix l3vpn;
  }

  // NEDs
  import tailf-ned-cisco-ios {
    prefix ios;
  }
  import tailf-ned-cisco-ios-xr {
   prefix cisco-ios-xr;
  }
  import junos {
    prefix junos;
  }
  import tailf-ned-alu-sr {
    prefix alu;
  }
  import tailf-ned-cisco-nx {
    prefix nx;
  }
  import tailf-ned-dell-ftos {
    prefix force10;
  }

  // NED IDs
  import cisco-ios-cli {
    prefix ios-ned-id;
  }
  import cisco-iosxr-cli {
   prefix iosxr-ned-id;
  }
  import juniper-junos-nc {
    prefix junos-ned-id;
  }
  import alu-sr-cli {
    prefix alu-ned-id;
  }
  import cisco-nx-cli {
    prefix nx-ned-id;
  }
  import dell-ftos-cli {
    prefix force10-ned-id;
  }


  // Package depenencies
  import cisco-etsi-nfvo {
    prefix cisco-nfvo;
  }
  import etsi-nfv-descriptors {
    prefix nfv;
  }
  import resource-allocator {
    prefix ralloc;
  }
  import ipaddress-allocator {
    prefix ipalloc;
  }

  identity l3vpn {
    base ncs:plan-component-type;
    description "L3VPN plan component";
  }

  identity data-centre {
    base ncs:plan-component-type;
    description "Data-centre plan component";
  }

  identity network-service {
    base ncs:plan-component-type;
    description "Network service plan component";
  }

  identity ip-addresses-allocated {
    base ncs:plan-state;
    description "Network service component state - " +
                "IP addresses have benn allocated";
  }

  identity vnfs-instantiated {
    base ncs:plan-state;
    description "Network service component state - " +
                "all VNFS have been spun up";
  }

  identity topology-created {
    base ncs:plan-state;
    description "Network service component state - " +
                "topoloogy connections have been created";
  }

  typedef config-format {
    type enumeration {
      enum cli;
      enum curly-braces;
      enum json;
      enum xml;
      enum yaml;
    }
  }

  grouping interface-leafrefs-grouping {
    choice interface-type {
      leaf ios-GigabitEthernet{
        when "derived-from(/ncs:devices/ncs:device" +
             "[ncs:name=current()/../device]/ncs:device-type" +
             "/ncs:cli/ncs:ned-id, 'ios-ned-id:cisco-ios-cli')";
        tailf:info "Cisco IOS Gigabit Ethernet interface";
        type leafref {
          path "deref(../device)/../ncs:config" +
               "/ios:interface/ios:GigabitEthernet/ios:name";
        }
      }
      leaf ios-xr-GigabitEthernet {
        when "derived-from(/ncs:devices/ncs:device" +
             "[ncs:name=current()/../device]/ncs:device-type" +
             "/ncs:cli/ncs:ned-id, 'iosxr-ned-id:cisco-iosxr-cli')";
        tailf:info "Cisco IOS-XR Gigabit Ethernet interface";
        type leafref {
          path "deref(../device)/../ncs:config" +
               "/cisco-ios-xr:interface" +
               "/cisco-ios-xr:GigabitEthernet/cisco-ios-xr:id";
        }
      }
      leaf ios-xr-TenGigE {
        when "derived-from(/ncs:devices/ncs:device" +
             "[ncs:name=current()/../device]/ncs:device-type" +
             "/ncs:cli/ncs:ned-id, 'iosxr-ned-id:cisco-iosxr-cli')";
        tailf:info "Cisco IOS-XR 10 Gigabit Ethernet interface";
        type leafref {
          path "deref(../device)/../ncs:config" +
               "/cisco-ios-xr:interface" +
               "/cisco-ios-xr:TenGigE/cisco-ios-xr:id";
        }
      }
      leaf junos-interface {
        when "derived-from(/ncs:devices/ncs:device" +
             "[ncs:name=current()/../device]/ncs:device-type" +
             "/ncs:netconf/ncs:ned-id, 'junos-ned-id:juniper-junos-nc')";
        tailf:info "Junos interface";
        type leafref {
          path "deref(../device)/../ncs:config/junos:configuration" +
               "/junos:interfaces/junos:interface/junos:name";
        }
      }
      leaf alu-interface {
        when "derived-from(/ncs:devices/ncs:device" +
             "[ncs:name=current()/../device]/ncs:device-type" +
             "/ncs:cli/ncs:ned-id, 'alu-ned-id:alu-sr-cli')";
        tailf:info "ALU interface";
        type leafref {
          path "deref(../device)/../ncs:config/alu:port/alu:port-id";
        }
      }
      leaf nx-Ethernet {
        when "derived-from(/ncs:devices/ncs:device" +
             "[ncs:name=current()/../device]/ncs:device-type" +
             "/ncs:cli/ncs:ned-id, 'nx-ned-id:cisco-nx-cli')";
        tailf:info "Cisco NX Ethernet interface";
        type leafref {
          path "deref(../device)/../ncs:config/nx:interface" +
               "/nx:Ethernet/nx:name";
        }
      }
      leaf nx-port-channel {
        when "derived-from(/ncs:devices/ncs:device" +
             "[ncs:name=current()/../device]/ncs:device-type" +
             "/ncs:cli/ncs:ned-id, 'nx-ned-id:cisco-nx-cli')";
        tailf:info "Cisco NX Port Channel interface";
        type leafref {
          path "deref(../device)/../ncs:config/nx:interface" +
               "/nx:port-channel/nx:name";
        }
      }
      leaf f10-GigabitEthernet {
        when "derived-from(/ncs:devices/ncs:device" +
             "[ncs:name=current()/../device]/ncs:device-type" +
             "/ncs:cli/ncs:ned-id, 'force10-ned-id:dell-ftos-cli')";
        tailf:info "Dell Force10 GigabitEthernet interface";
        type leafref {
          path "deref(../device)/../ncs:config/force10:interface" +
               "/force10:GigabitEthernet/force10:id";
        }
      }
    }
  }

  grouping sap-topology-connection-grouping {
    leaf sapd {
      type leafref {
        path "deref(../../nsd)/../nfv:sapd/nfv:id";
      }
    }

    leaf device {
      type leafref {
        path "/ncs:devices/ncs:device/ncs:name";
      }
    }

    uses interface-leafrefs-grouping;
  }

  container tme-demo {
    list default-ns-topology-connections {
      key nsd;
      leaf nsd {
        type leafref {
          path "/nfv:nfv/nfv:nsd/nfv:id";
        }
      }

      list sap-topology-connection {
        key sapd;
        uses sap-topology-connection-grouping;
      }
    }

    list tenant {
      key name;
      leaf name {
        tailf:info "Unique service id";
        tailf:cli-allow-range;
        type string;
      }

      description "Tenant";
      uses ncs:plan-data;
      uses ncs:service-data;
      ncs:servicepoint tme-demo-servicepoint;

      container l3vpn {
        tailf:info "Layer3 VPN parameters";
        presence true;

        leaf route-distinguisher {
          tailf:info "Route distinguisher/target identifier unique for the VPN";
          type uint32 {
            range "0..65535";
          }
          default 65535;
        }

        leaf qos-policy {
          tailf:info "VPN QoS Policy";
          type leafref {
            path "/l3vpn:qos/l3vpn:qos-policy/l3vpn:name";
          }
        }

        list endpoint {
          key "id";
          leaf id{
            tailf:info "Endpoint identifier";
            type string;
          }

          leaf ce-device {
            tailf:info "CE endpoint device";
            type leafref {
              path "/ncs:devices/ncs:device/ncs:name";
            }
            must "/ncs:devices/ncs:device-group[ncs:name='C']" +
                 "/ncs:device-name[.=current()]" {
              error-message "The device must be in the C device group";
            }
            must "count(/l3vpn:topology/l3vpn:connection" +
                 "/l3vpn:endpoint-1[l3vpn:device=current()])>0 or " +
                 "count(/l3vpn:topology/l3vpn:connection" +
                 "/l3vpn:endpoint-2[l3vpn:device=current()])>0" {
              error-message "The device must have a topology connection";
            }
            mandatory true;
          }

          leaf ce-interface {
            tailf:info "CE local GigabitEthernet interface";
            type leafref {
              path "deref(../ce-device)/../ncs:config" +
                   "/ios:interface/ios:GigabitEthernet/ios:name";
            }
            default "0/1";
          }

          leaf ip-network {
            tailf:info "CE interface local private network";
            type inet:ip-prefix;
            default "10.0.0.0/24";
          }

          leaf bandwidth {
            tailf:info "Endpoint bandwidth in bps";
            type uint32;
            default 10000000;
          }

          leaf as-number {
            tailf:info "CE device AS Number";
            type uint32 {
              range "0..65535";
            }
            default 500;
          }
        }
      }

      container data-centre {
        tailf:info "Data centre connectivity parameters";
        presence true;

        leaf vlan {
          tailf:info "Data centre tenant VLAN";
          type uint32;
          default 500;
        }

        leaf ip-network {
          tailf:info "The private IP network";
          type inet:ip-prefix;
          default "50.0.0.0/24";
        }

        leaf preserve-vlan-tags {
          type boolean;
          default false;
        }

        list endpoint {
          key "device compute";

          leaf device {
            tailf:info "TOR switch";
            type leafref {
              path "/ncs:devices/ncs:device/ncs:name";
            }
          }

          leaf compute {
            tailf:info "Compute node (not used)";
            type enumeration {
              enum compute0;
              enum compute1;
              enum compute2;
              enum compute3;
              enum compute4;
            }
          }

          uses interface-leafrefs-grouping;

          leaf connect-multiple-vlans {
            tailf:info "Make the accessport a trunk";
            type boolean;
            default false;
          }
        }
      }

      container nfvo {
        tailf:info "NFVO parameters for network services";
        presence true;

        list network-service {
          key name;
          leaf name {
            type string;
          }

          leaf nsd {
            type leafref {
              path "/nfv:nfv/nfv:nsd/nfv:id";
            }
            mandatory true;
          }

          leaf flavour {
            type leafref {
              path "deref(../nsd)/../nfv:df/nfv:id";
            }
            mandatory true;
          }

          leaf vnfm {
            type leafref {
              path "/ncs:devices/ncs:device/ncs:name";
            }
            must "/ncs:devices/ncs:device-group[ncs:name='VNFM']" +
                 "/ncs:device-name[.=current()]" {
              error-message "The device must be in the VNFM device group";
            }
            default "esc0";
          }

          choice connections-choice {
            mandatory true;
            leaf use-default-topology-connections {
              when "/tme-demo:tme-demo" +
                   "/default-ns-topology-connections[nsd=current()/../nsd]";
              type empty;
            }
            list sap-topology-connection {
              key sapd;
              uses sap-topology-connection-grouping;
            }
          }
        }
      }

      leaf touch-date {
        type string;
      }
    }
  }

  augment "/nfv:nfv/cisco-nfvo:internal/cisco-nfvo:netconf-deployment-result/cisco-nfvo:vm-group" {
    leaf vms-scaling {
      type uint8;
      config false;
//      tailf:cdb-oper {
//        tailf:persistent true;
//      }
    }
  }

  augment "/ncs:devices/ncs:device" {
    tailf:action get-configuration {
      tailf:info "Get full device configuration";
      tailf:actionpoint get-device-configuration;

      input {
        leaf format {
          type config-format;
        }

        leaf service-meta-data {
          type boolean;
        }
      }

      output {
        leaf format {
          type config-format;
        }

        leaf config {
          type string;
        }
      }
    }
  }

}
